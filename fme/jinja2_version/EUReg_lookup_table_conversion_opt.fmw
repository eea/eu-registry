FME workspace EUReg_lookup_table_conversion_opt.fmw
Shutdown Python:
      # Script to split lookup tables into separate tables per country

Parameters:
- DB_CONNECTION = EUReg   # SQL Server Connection
- TOP_PERCENT_LIMIT = 100   # Process only first percent of records
- COUNTRY_CODE = CZ   # Country Code
- PRODUCTION_SITE_FILE = ProductionSite.xml   # Production Site File
- PRODUCTION_FACILITY_FILE = ProductionFacility.xml   # Production Facility File
- PRODUCTION_INSTALLATION_FILE = ProductionInstallation.xml   # Production Installation File
- PRODUCTION_INSTALLATION_PART_FILE = ProductionInstallationPart.xml   # Production Installation Part File

Creator
    GEOMTYPE = Geometry Object
    NUM = 1
    CREATED -> SQLExecutor [INITIATOR]
SQLExecutor
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCENT_LIMIT))PERCENT
      countryCode as countryId,
      reportingYear,
      localId as inspireId_localId,
      namespace as inspireId_namespace,
      siteName,
      gmlId,
      x_4258 as longitude,
      y_4258 as latitude
      from dbo.ProductionSite
      where countryCode = '$(COUNTRY_CODE)'
    RESULT -> Jinja2Wrapper-PS [Features]
Jinja2Wrapper-PS
    TEMPLATE_FILE = production_site_template.jinja2.xml
    Html -> AttributeCreator_PSFile
AttributeCreator_PSFile
    ATTR_TABLE = SET_TO ProductionSiteFile = $(COUNTRY_CODE)_$(PRODUCTION_SITE_FILE)
    -> PS_file [text_line]
PS_file: FeatureWriter
    DATASET = @Value(ProductionSiteFile)
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SQLExecutor_2 [INITIATOR]
SQLExecutor_2
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCENT_LIMIT))PERCENT
      pf.countryCode as countryId,
      pf.reportingYear as reportingYear,
      pf.localId as inspireId_localId,
      pf.namespace as inspireId_namespace,
      pf.gmlId as gmlId,
      pf.x_4258 as longitude,
      pf.y_4258 as latitude,
      pf.facilityName as facilityName,
      pf.parentCompanyName as parentCompanyName,
      pf.parentCompanyURL as parentCompanyURL,
      pf.parentCompanyConfidentiality as parentCompanyConfidentiality,
      ps.localId as hostingSite,
      pf.EPRTRAnnexIMainActivity as mainActivity,
      pf.status as status
      from dbo.ProductionFacility pf
      left join dbo.ProductionSite ps
      on pf.siteId = ps.id
      where pf.countryCode = '$(COUNTRY_CODE)'
    RESULT -> Jinja2Wrapper-PF [Features]
Jinja2Wrapper-PF
    TEMPLATE_FILE = production_facility_template.jinja2.xml
    Html -> AttributeCreator_PFFile
AttributeCreator_PFFile
    ATTR_TABLE = SET_TO ProductionFacilityFile = $(COUNTRY_CODE)_$(PRODUCTION_FACILITY_FILE)
    -> PF_File [text_line]
PF_File: FeatureWriter
    DATASET = @Value(ProductionFacilityFile)
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SQLExecutor_3 [INITIATOR]
SQLExecutor_3
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCENT_LIMIT))PERCENT
      pi.countryCode as countryId,
      pi.reportingYear,
      pi.localId as inspireId_localId,
      pi.namespace as inspireId_namespace,
      pi.gmlId,
      pi.x_4258 as longitude,
      pi.y_4258 as latitude,
      pi.installationName,
      pi.IEDAnnexIMainActivity as mainActivity,
      oa.otherActivities as otherActivities,
      pi.status,
      px.dateOfGrantings,
      px.permitURLs
      from dbo.ProductionInstallation pi left join
      (select installationId, STRING_AGG (otherActivity, ',') as otherActivities
      from dbo.ProductionInstallationIEDOtherActivity group by installationId ) oa
      on oa.installationId = pi.id
      left join
      (select installationId,
      STRING_AGG (ISNULL(convert(varchar,dateOfGranting,112),'NULL'), ',') as dateOfGrantings,
      STRING_AGG (ISNULL(permitURL,'NULL'), ',') as permitURLs
      from dbo.ProductionInstallationPermitDetails group by installationId) px
      on px.installationId = pi.id
      where pi.countryCode = '$(COUNTRY_CODE)'
    RESULT -> Jinja2Wrapper-PI [Features]
Jinja2Wrapper-PI
    TEMPLATE_FILE = production_installation_template.jinja2.xml
    Html -> AttributeCreator_PIFile
AttributeCreator_PIFile
    ATTR_TABLE = SET_TO ProductionInstallationFile = $(COUNTRY_CODE)_$(PRODUCTION_INSTALLATION_FILE)
    -> PI_File [text_line]
PI_File: FeatureWriter
    DATASET = @Value(ProductionInstallationFile)
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SQLExecutor_4 [INITIATOR]
SQLExecutor_4
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCENT_LIMIT))PERCENT
      pip.countryCode as countryId,
      pip.reportingYear,
      pip.localId as inspireId_localId,
      pip.namespace as inspireId_namespace,
      pip.installationPartName,
      pip.plantType,
      pip.gmlId,
      pip.x_4258 as longitude,
      pip.y_4258 as latitude,
      pip.status
      from dbo.ProductionInstallationPart pip left join
      (select installationPartId, STRING_AGG (derogation, ',') as derogations
      from dbo.ProductionInstallationPartDerogation group by installationPartId ) pd
      on pd.installationPartId = pip.id
      where pip.countryCode = '$(COUNTRY_CODE)'
    RESULT -> Jinja2Wrapper-PIP [Features]
Jinja2Wrapper-PIP
    TEMPLATE_FILE = production_installation_part_template.jinja2.xml
    Html -> AttributeCreator_PIPFile
AttributeCreator_PIPFile
    ATTR_TABLE = SET_TO ProductionInstallationPartFile = $(COUNTRY_CODE)_$(PRODUCTION_INSTALLATION_PART_FILE)
    -> PIP_file [text_line]
PIP_file: FeatureWriter
    DATASET = @Value(ProductionInstallationPartFile)
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

FME custom transformer Jinja2Wrapper
Transformer is a wrapper around standard Jinja2 template engine

Parameters:
- TEMPLATE_FILE =   # Select the template file

FirstRowVariables (input)
    -> FirstRow
FirstRow: Sampler
    RATE = 1
    SAMPLE_MODE = No
    SAMPLE_TYPE_LONG = First N Features
    SAMPLED -> AttributeCreator_2
AttributeCreator_2
    ATTR_TABLE = SET_TO _jinjaDataClass = globalFirstRow
    -> PythonCaller
NameValuePairs (input)
    -> AttributeCreator
AttributeCreator
    ATTR_TABLE = SET_TO _jinjaDataClass = globalKeyValue
    -> PythonCaller
Features (input)
    -> FirstRow_2
FirstRow_2: Sampler
    RATE = 1
    SAMPLE_MODE = No
    SAMPLE_TYPE_LONG = First N Features
    SAMPLED -> ParameterFetcher
    NOT_SAMPLED -> PythonCaller
ParameterFetcher
    ATTR_LIST = _templateFile $(TEMPLATE_FILE) _workingDir $(FME_MF_DIR_USERTYPED)
    -> PythonCaller
PythonCaller
    NEW_ATTRIBUTES = _templater_output_id
    PYTHONSOURCE:
      import sys
      import os
      import pip
      import uuid
      import pathlib
      import fme
      import fmeobjects
      import subprocess


      templater_outputs = {}

      class FeatureProcessor(object):
          def __init__(self):
              self.data = []
              self.templater_output_id = str(uuid.uuid1())
              self.globals = {}
              self.template_file = None
              self.working_dir = None

          def input(self, feature):
              # Need to transform the feature with its list attributes in a python dict
              # List attributes are tricky because they are presented as columns rather than rows
              entry = {}
              local_lists= {}
              feature.setAttribute("_templater_output_id", self.templater_output_id)

              att_names = feature.getAllAttributeNames()

              if "_templateFile" in att_names:
                  self.template_file = feature.getAttribute("_templateFile")

              if "_workingDir" in att_names:
                  self.working_dir = feature.getAttribute("_workingDir")

              if "_jinjaDataClass" in att_names:
                  for att in att_names:
                      self.globals[att] = feature.getAttribute(att)
                  return


              for att in att_names:
                  att_split = att.split('{')
                  if len(att_split) > 1:
                  # List attribute
                      att_split = [att_split[0],att_split[1].split('.')[1]]
                      list_name = att_split[0]
                      field_name = att_split[1]
                      list_att_name = '{}{{}}.{}'.format(list_name, field_name)
                      values = feature.getAttribute(list_att_name)
                      if list_name not in local_lists:
                          local_lists[list_name] =[{} for _ in values]
                      for idx, v in enumerate(values):
                          local_lists[list_name][idx][field_name] = v
                  else:
                  # Regualr attribute
                      entry[att] = feature.getAttribute(att)
              # Now add the lists of dict in the main entry
              for list_name, value in local_lists.items():
                  entry[list_name] = value
              self.data.append(entry)
              self.pyoutput(feature)

          def close(self):
              global templater_outputs
              # Install jinja2 if not available but only on local deployments not on server
              if (FME_MacroValues['FME_SERVER_HOST']==''):
                  print("Running on desktop machine")
                  #installed_pkgs = set([pkg.key for pkg in pip.get_installed_distributions()])
                  installed_pkgs = sys.modules.keys()
                  if 'jinja2' not in installed_pkgs:
                      print("Installing jinja2")
                      try:
                          #subprocess.call(["pip", "install","target","." ,"jinja2"])
                          if int(pip.__version__.split('.')[0])>9:
                             from pip._internal import main
                          else:
                              from pip import main
                          main(["install","--user","jinja2",])
                      except SystemExit as e:
                          print(e)
                          return
                      sys.path.append(os.getcwd())
              import jinja2

              if self.template_file is None or len(self.data)==0:
                  return

              loader = jinja2.FileSystemLoader(self.working_dir)

              #with open(pathlib.Path(self.working_dir, self.template_file)) as file_:
              #    template = jinja2.Template(file_.read())

              try:
                  env = jinja2.Environment(loader=loader, autoescape=jinja2.select_autoescape(['xml','gml']))
                  template = env.get_template(self.template_file)
              except jinja2.TemplateNotFound as e:
                  print(
                  """
                  Error finding Template!
                  --------------------------
                  Error:    {}
                  Name: {}
                  """.format(e.message, e.name))
                  return
              except jinja2.TemplateSyntaxError as e:
                  print(
                  """
                  Syntax error in template!
                  --------------------------
                  Error: {}
                  Name: {}
                  LineNo: {}
                  """.format(e.message, e.name, e.lineno))
                  return
              templater_outputs[self.templater_output_id] = template.render(features = self.data, **self.globals)
    PYTHONSYMBOL = FeatureProcessor
    -> FeatureHolder
    -> Initiator (output)
FeatureHolder
    -> FirstOnly
FirstOnly: Sampler
    RATE = 1
    SAMPLE_MODE = No
    SAMPLE_TYPE_LONG = First N Features
    SAMPLED -> AttributeKeeper
AttributeKeeper
    KEEP_ATTRS = _templater_output_id
    -> WriteOutputHtml
WriteOutputHtml: PythonCaller
    NEW_ATTRIBUTES = html
    PYTHONSOURCE:
      import fme
      import fmeobjects

      def processFeature(feature):
          global templater_outputs
          output_id = feature.getAttribute("_templater_output_id")
          feature.setAttribute("html", templater_outputs[output_id])
    PYTHONSYMBOL = processFeature
    -> AttributeRemover
AttributeRemover
    REMOVE_ATTRS = _tempitaLocalId
    -> Html (output)
Html (output)
Initiator (output)
