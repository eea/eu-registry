FME workspace EUReg_lookup_table_conversion_py_callers.fmw
Shutdown Python:
      # Script to split lookup tables into separate tables per country

      from collections import defaultdict
      from lxml import etree
      import os

      feature_names = [
          "ProductionFacility",
          "ProductionSite",
          "ProductionInstallationPart",
          "ProductionInstallation",
      ]

      for feature_name in feature_names:
          print("###Starting", feature_name)
          filename = '{}.xml'.format(feature_name)

          input_data = etree.parse(filename)
          feature_nodes = input_data.findall(feature_name)

          output_data = defaultdict(list)

          if not os.path.exists(feature_name):
              os.makedirs(feature_name)

          for node in feature_nodes:
              country_id = node.find('countryId').attrib.values()[0]
              output_data[country_id].append(node)

          for country_id, nodes in output_data.items():
              print("Starting ", country_id)
              out_filename = '{}_{}'.format(country_id, filename)
              output_file = os.path.join(feature_name, out_filename)

              document_node = etree.Element('data')
              root = etree.ElementTree(document_node)

              for node in nodes:
                  document_node.append(node)

              root.write(output_file,
                         encoding=None,
                         method="xml",
                         pretty_print=True)

Parameters:
- DB_CONNECTION = teal_eureg   # SQL Server Connection
- TOP_PERCERNT_LIMIT = 100   # Process only first percent of records
- PRODUCTION_SITE_FILE = ProductionSite.xml   # Production Site File
- PRODUCTION_FACILITY_FILE = ProductionFacility.xml   # Production Facility File
- PRODUCTION_INSTALLATION_FILE = ProductionInstallation.xml   # Production Installation File
- PRODUCTION_INSTALLATION_PART_FILE = ProductionInstallationPart.xml   # Production Installation Part File

Creator
    GEOMTYPE = Geometry Object
    NUM = 1
    CREATED -> SQLExecutor [INITIATOR]
SQLExecutor
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCERNT_LIMIT))PERCENT
      countryCode as countryId,
      reportingYear,
      localId as inspireId_localId,
      namespace as inspireId_namespace,
      siteName,
      gmlId,
      x_4258 as longitude,
      y_4258 as latitude
      from dbo.ProductionSite
    RESULT -> PythonCaller
PythonCaller
    NEW_ATTRIBUTES = text_line_data
    PYTHONSOURCE:
      import fme
      import fmeobjects
      import html

      # Template Class Interface:
      # When using this class, make sure its name is set as the value of
      # the 'Class or Function to Process Features' transformer parameter
      class FeatureProcessor(object):
          def __init__(self):
              self.xml_list = []
              self.text_line_data = ''
          def input(self,feature):
              tmp = '    <ProductionSite>\n\
              <countryId xlink:href="%s"></countryId>\n\
              <reportingYear>%s</reportingYear>\n\
              <inspireId>\n\
                  <localId>%s</localId>\n\
                  <namespace>%s</namespace>\n\
              </inspireId>\n\
              <siteName>\n\
                  <nameOfFeature>%s</nameOfFeature>\n\
              </siteName>\n\
              <location>\n\
                  <gml:Point xmlns:gml="http://www.opengis.net/gml/3.2" gml:id="%s" srsDimension="2">\n\
                      <gml:pos>%s %s</gml:pos>\n\
                  </gml:Point>\n\
              </location>\n\
          </ProductionSite>' % (feature.getAttribute('countryId'),\
          feature.getAttribute('reportingYear'),\
          feature.getAttribute('inspireId_localId'),\
          feature.getAttribute('inspireId_namespace'),\
          html.escape(feature.getAttribute('siteName')),\
          feature.getAttribute('gmlId'),\
          feature.getAttribute('longitude'),\
          feature.getAttribute('latitude'))
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'
              newFeature = fmeobjects.FMEFeature()
              newFeature.setAttribute("text_line_data", self.text_line_data)
              self.pyoutput(newFeature)
    PYTHONSYMBOL = FeatureProcessor
    -> PS_file [text_line]
PS_file: FeatureWriter
    DATASET = $(PRODUCTION_SITE_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SQLExecutor_2 [INITIATOR]
SQLExecutor_2
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCERNT_LIMIT))PERCENT
      pf.countryCode as countryId,
      pf.reportingYear as reportingYear,
      pf.localId as inspireId_localId,
      pf.namespace as inspireId_namespace,
      pf.gmlId as gmlId,
      pf.x_4258 as longitude,
      pf.y_4258 as latitude,
      pf.facilityName as facilityName,
      pf.parentCompanyName as parentCompanyName,
      pf.parentCompanyURL as parentCompanyURL,
      pf.parentCompanyConfidentiality as parentCompanyConfidentiality,
      ps.localId as hostingSite,
      pf.EPRTRAnnexIMainActivity as mainActivity,
      pf.status as status
      from dbo.ProductionFacility pf
      left join dbo.ProductionSite ps
      on pf.siteId = ps.id
    RESULT -> PythonCaller_2
PythonCaller_2
    NEW_ATTRIBUTES = text_line_data
    PYTHONSOURCE:
      import fme
      import fmeobjects
      import html

      # Template Class Interface:
      # When using this class, make sure its name is set as the value of
      # the 'Class or Function to Process Features' transformer parameter
      class FeatureProcessor(object):
          def __init__(self):
              self.xml_list = []
              self.text_line_data = ''
          def input(self,feature):
              tmp = '    <ProductionFacility>\n\
              <countryId xlink:href="%s"></countryId>\n\
              <reportingYear>%s</reportingYear>\n\
              <inspireId>\n\
                  <localId>%s</localId>\n\
                  <namespace>%s</namespace>\n\
              </inspireId>\n\
      		<geometry>\n\
                  <gml:Point xmlns:gml="http://www.opengis.net/gml/3.2" gml:id="%s" srsDimension="2">\n\
                      <gml:pos>%s %s</gml:pos>\n\
                  </gml:Point>\n\
              </geometry>\n\
              <facilityName>\n\
                  <nameOfFeature>%s</nameOfFeature>\n\
              </facilityName>\n\
      		<EUReg:parentCompany>\n\
      			<EUReg:ParentCompanyDetails>\n\
      				<EUReg:parentCompanyName>%s</EUReg:parentCompanyName>\n\
      				<EUReg:parentCompanyURL>%s</EUReg:parentCompanyURL>\n\
      				<EUReg:confidentialityReason xlink:href="http://dd.eionet.europa.eu/vocabulary/euregistryonindustrialsites/ReasonValue/%s"></EUReg:confidentialityReason>\n\
      			</EUReg:ParentCompanyDetails>\n\
      		</EUReg:parentCompany>\n\%s\
      		<EPRTRAnnexIActivity>\n\
      			<EUReg:EPRTRAnnexIActivityType>\n\
      				<EUReg:mainActivity xlink:href="http://dd.eionet.europa.eu/vocabulary/euregistryonindustrialsites/EPRTRAnnexIActivityValue/%s"></EUReg:mainActivity>\n\
      			</EUReg:EPRTRAnnexIActivityType>\n\
      		</EPRTRAnnexIActivity>\n\
      		<status>\n\
                  <pf:statusType xlink:href="http://dd.eionet.europa.eu/vocabulary/euregistryonindustrialsites/ConditionOfFacilityValue/%s"></pf:statusType>\n\
      			<pf:validFrom xsi:nil="true"></pf:validFrom>\n\
              </status>\n\
          </ProductionFacility>' % (feature.getAttribute('countryId'),\
          feature.getAttribute('reportingYear'),\
          feature.getAttribute('inspireId_localId'),\
          feature.getAttribute('inspireId_namespace'),\
      	feature.getAttribute('gmlId'),\
          feature.getAttribute('longitude'),\
          feature.getAttribute('latitude'),\
      	html.escape(feature.getAttribute('facilityName')),\
      	html.escape(feature.getAttribute('parentCompanyName')),\
      	feature.getAttribute('parentCompanyURL'),\
      	feature.getAttribute('parentCompanyConfidentiality'),\
          '		<hostingSite xlink:href="#_%s"></hostingSite>\n' % (feature.getAttribute('hostingSite'),) if feature.getAttribute('hostingSite') else '',\
      	feature.getAttribute('mainActivity'),\
      	feature.getAttribute('status'))
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PF_File [text_line]
PF_File: FeatureWriter
    DATASET = $(PRODUCTION_FACILITY_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SQLExecutor_3 [INITIATOR]
SQLExecutor_3
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCERNT_LIMIT))PERCENT
      pi.countryCode as countryId,
      pi.reportingYear,
      pi.localId as inspireId_localId,
      pi.namespace as inspireId_namespace,
      pi.gmlId,
      pi.x_4258 as longitude,
      pi.y_4258 as latitude,
      pi.installationName,
      pi.IEDAnnexIMainActivity as mainActivity,
      oa.otherActivities as otherActivities,
      pi.status,
      px.dateOfGrantings,
      px.permitURLs
      from dbo.ProductionInstallation pi left join
      (select installationId, STRING_AGG (otherActivity, ',') as otherActivities
      from dbo.ProductionInstallationIEDOtherActivity group by installationId ) oa
      on oa.installationId = pi.id
      left join
      (select installationId,
      STRING_AGG (ISNULL(convert(varchar,dateOfGranting,112),'NULL'), ',') as dateOfGrantings,
      STRING_AGG (ISNULL(permitURL,'NULL'), ',') as permitURLs
      from dbo.ProductionInstallationPermitDetails group by installationId) px
      on px.installationId = pi.id
    RESULT -> PythonCaller_3
PythonCaller_3
    NEW_ATTRIBUTES = text_line_data
    PYTHONSOURCE:
      import fme
      import fmeobjects
      from datetime import datetime
      import html

      # Template Class Interface:
      # When using this class, make sure its name is set as the value of
      # the 'Class or Function to Process Features' transformer parameter
      class FeatureProcessor(object):
          def __init__(self):
              self.xml_list = []
              self.text_line_data = ''
          def input(self,feature):
              otherActivity = ''
              permits = ''
              if feature.getAttribute('otherActivities'):
                  otherActivitiesList = feature.getAttribute('otherActivities').split(",")
                  for x in otherActivitiesList:
                      otherActivity += '                <EUReg:otherActivity xlink:href="http://dd.eionet.europa.eu/vocabulary/euregistryonindustrialsites/IEDAnnexIActivityValue/%s"></EUReg:otherActivity>\n'%(x,)
              if feature.getAttribute('dateOfGrantings'):
                  dateOfGrantings_list = feature.getAttribute('dateOfGrantings').split(",")
                  permitURLs_list = feature.getAttribute('permitURLs').split(",")
                  for i in range(len(dateOfGrantings_list)):
                      permits += '        <permit>\n'
                      if dateOfGrantings_list[i] != 'NULL' :
                          permits += '            <dateOfGranting>%s</dateOfGranting>\n'%(datetime.strptime(dateOfGrantings_list[i],'%Y%m%d').date(),)
                      if permitURLs_list[i] != 'NULL':
                          permits += '            <permitURL>%s</permitURL>\n'%(html.escape(permitURLs_list[i]),)
                      permits += '        </permit>\n'
              tmp = '    <ProductionInstallation>\n\
              <countryId xlink:href="%s"></countryId>\n\
              <reportingYear>%s</reportingYear>\n\
              <inspireId>\n\
                  <localId>%s</localId>\n\
                  <namespace>%s</namespace>\n\
              </inspireId>\n\
              <pointGeometry>\n\
                  <gml:Point xmlns:gml="http://www.opengis.net/gml/3.2" gml:id="%s" srsDimension="2">\n\
                      <gml:pos>%s %s</gml:pos>\n\
                  </gml:Point>\n\
              </pointGeometry>\n\
              <installationName>\n\
                  <nameOfFeature>%s</nameOfFeature>\n\
              </installationName>\n\
              <IEDAnnexIActivity>\n\
                  <EUReg:IEDAnnexIActivityType>\n\
                      <EUReg:mainActivity xlink:href="http://dd.eionet.europa.eu/vocabulary/euregistryonindustrialsites/IEDAnnexIActivityValue/%s"></EUReg:mainActivity>\n%s\
                  </EUReg:IEDAnnexIActivityType>\n\
              </IEDAnnexIActivity>\n\
              <status>\n\
                  <pf:StatusType>\n\
                      <pf:statusType xlink:href="http://dd.eionet.europa.eu/vocabulary/euregistryonindustrialsites/ConditionOfFacilityValue/%s"></pf:statusType>\n\
                      <pf:validFrom xsi:nil="true"></pf:validFrom>\n\
                  </pf:StatusType>\n\
              </status>\n%s\
          </ProductionInstallation>' % (feature.getAttribute('countryId'),\
          feature.getAttribute('reportingYear'),\
          feature.getAttribute('inspireId_localId'),\
          feature.getAttribute('inspireId_namespace'),\
          feature.getAttribute('gmlId'),\
          feature.getAttribute('longitude'),\
          feature.getAttribute('latitude'),\
          html.escape(feature.getAttribute('installationName')),\
          feature.getAttribute('mainActivity'),\
          otherActivity,\
          feature.getAttribute('status'),\
          permits)
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PI_file [text_line]
PI_file: FeatureWriter
    DATASET = $(PRODUCTION_INSTALLATION_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SQLExecutor_4 [INITIATOR]
SQLExecutor_4
    COMBINE_ATTRS = Result Attributes Only
    COMBINE_GEOM = Initiator Geometry Only
    DATASET = $(DB_CONNECTION)
    FORMAT = MSSQL_ADO
    MSSQL_ADO_COMMAND_TIMEOUT = 30
    MSSQL_ADO_CREATE_FEATURE_TABLES_FROM_DATA = Yes
    MSSQL_ADO_NAMED_CONNECTION = $(DB_CONNECTION)
    MSSQL_ADO_QUERY_FEATURE_TYPES_FOR_MERGE_FILTERS = Yes
    SQL_STATEMENT:
      select TOP($(TOP_PERCERNT_LIMIT))PERCENT
      pip.countryCode as countryId,
      pip.reportingYear,
      pip.localId as inspireId_localId,
      pip.namespace as inspireId_namespace,
      pip.installationPartName,
      pip.plantType,
      pip.gmlId,
      pip.x_4258 as longitude,
      pip.y_4258 as latitude,
      pip.status
      from dbo.ProductionInstallationPart pip left join
      (select installationPartId, STRING_AGG (derogation, ',') as derogations
      from dbo.ProductionInstallationPartDerogation group by installationPartId ) pd
      on pd.installationPartId = pip.id
    RESULT -> PythonCaller_4
PythonCaller_4
    NEW_ATTRIBUTES = text_line_data
    PYTHONSOURCE:
      import fme
      import fmeobjects
      import html

      # Template Class Interface:
      # When using this class, make sure its name is set as the value of
      # the 'Class or Function to Process Features' transformer parameter
      class FeatureProcessor(object):
          def __init__(self):
              self.xml_list = []
              self.text_line_data = ''
          def input(self,feature):
              derogations = ''
              if feature.getAttribute('derogations'):
                  derogations_list = feature.getAttribute('derogations').split(",")
                  for x in derogations_list:
                      derogations += '        <derogations xlink:href="http://dd.eionet.europa.eu/vocabulary/euregistryonindustrialsites/DerogationValue/%s"></derogations>\n'%(x,)
              tmp = '    <ProductionInstallationPart>\n\
              <countryId xlink:href="%s"></countryId>\n\
              <reportingYear>%s</reportingYear>\n\
              <inspireId>\n\
                  <localId>%s</localId>\n\
                  <namespace>%s</namespace>\n\
              </inspireId>\n\
              <installationPartName>\n\
                  <nameOfFeature>%s</nameOfFeature>\n\
              </installationPartName>\n\
              <plantType xlink:href="http://dd.eionet.europa.eu/vocabulary/euregistryonindustrialsites/PlantTypeValue/%s"></plantType>\n\
              <pointGeometry>\n\
                  <gml:Point xmlns:gml="http://www.opengis.net/gml/3.2" gml:id="%s" srsDimension="2">\n\
                      <gml:pos>%s %s</gml:pos>\n\
                  </gml:Point>\n\
              </pointGeometry>\n\
              <status>\n\
                  <pf:statusType xlink:href="http://dd.eionet.europa.eu/vocabulary/euregistryonindustrialsites/ConditionOfFacilityValue/%s"></pf:statusType>\n\
      			<pf:validFrom xsi:nil="true"></pf:validFrom>\n\
              </status>\n%s\
          </ProductionInstallationPart>' % (feature.getAttribute('countryId'),\
          feature.getAttribute('reportingYear'),\
          feature.getAttribute('inspireId_localId'),\
          feature.getAttribute('inspireId_namespace'),\
          html.escape(feature.getAttribute('installationPartName')),\
          feature.getAttribute('plantType'),\
          feature.getAttribute('gmlId'),\
          feature.getAttribute('longitude'),\
          feature.getAttribute('latitude'),\
          feature.getAttribute('status'),\
          derogations)
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PIP_file [text_line]
PIP_file: FeatureWriter
    DATASET = $(PRODUCTION_INSTALLATION_PART_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
