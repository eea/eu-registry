FME workspace EUReg_lookup_table_conversion.fmw

Parameters:
- SourceDataset_MSSQL_ADO = teal_eureg   # SQL Server Connection
- PRODUCTION_SITE_FILE = ProductionSite.xml   # Production Site File
- PRODUCTION_FACILTY_FILE = ProductionFacility.xml   # Production Facility File
- PRODUCTION_INSTALLATION_FILE = ProductionInstallation.xml   # Production Installation File
- PRODUCTION_INSTALLATION_PART_FILE = ProductionInstallationPart.xml   # Production Installation Part File
- ZIP_PATH = eu_registry_lookup_tables.zip   # Destination Zip File

Readers:
- MSSQL_ADO_1: MSSQL_ADO from $(SourceDataset_MSSQL_ADO)

ProductionFacility (reader MSSQL_ADO_1)
    attributes: id identity, facilityName nvarchar(150), facilityNameConfidentiality varchar(25), parentCompanyName nvarchar(200), parentCompanyURL nvarchar(2048), parentCompanyConfidentiality varchar(25), status varchar(25), localId nvarchar(200), namespace nvarchar(200), identifier varchar(200), identifierScheme varchar(200), EPRTRAnnexIMainActivity varchar(25), remarks nvarchar(500), x_3857 integer, y_3857 integer, x_4326 float, y_4326 float, x_4258 float, y_4258 float, shape_wm image, facilityType varchar(25), streetName nvarchar(100), buildingNumber nvarchar(100), city nvarchar(100), postalCode nvarchar(100), addressConfidentiality varchar(25), dateOfStartOfOperation date, siteId integer, gmlId varchar(200), controlFileId integer,
      countryCode varchar(2), reportingYear integer
    -> FeatureJoiner [LEFT]
ProductionInstallation (reader MSSQL_ADO_1)
    attributes: id identity, installationName nvarchar(200), installationNameConfidentiality varchar(25), baselineReportIndicator varchar(25), siteVisitNumber integer, siteVisitURL nvarchar(100), IEDAnnexIMainActivity varchar(25), localId varchar(200), namespace varchar(200), identifier varchar(200), identifierScheme varchar(200), x_3857 integer, y_3857 integer, x_4326 float, y_4326 float, x_4258 float, y_4258 float, shape_wm image, remarks nvarchar(500), status varchar(25), publicEmissionMonitoring nvarchar(100), publicEmissionMonitoringURL nvarchar(2048), installationType varchar(25), dateOfStartOfOperation date, facilityId integer, gmlId varchar(200), controlFileId integer, countryCode varchar(2), reportingYear integer, NUTS_1 integer,
      NUTS_2 integer, NUTS_3 integer
    -> FeatureJoiner_2 [LEFT]
    -> FeatureJoiner_3 [LEFT]
ProductionInstallationIEDOtherActivity (reader MSSQL_ADO_1)
    attributes: Id identity, otherActivity varchar(25), installationId integer, controlFileId integer
    -> FeatureJoiner_2 [RIGHT]
FeatureJoiner_2
    ATTR_CONFLICT_RES = Use Left
    GEOMETRY_HANDLING = Use Left
    JOIN_KEYS = id installationId NUM
    JOIN_MODE = Inner
    JOINED -> ListBuilder
    UNJOINED_LEFT -> FeatureJoiner_4 [LEFT]
    UNJOINED_LEFT -> FeatureJoiner_5 [LEFT]
ListBuilder
    GROUPS_ORDERED = No
    GROUP_BY = id
    LIST_ATTRS_TO_INCLUDE = otherActivity
    LIST_NAME = list_other_activity
    -> FeatureJoiner_3 [RIGHT]
FeatureJoiner_3
    ATTR_CONFLICT_RES = Use Left
    GEOMETRY_HANDLING = Use Left
    JOIN_KEYS = id id AUTO
    JOIN_MODE = Inner
    JOINED -> FeatureJoiner_4 [LEFT]
    JOINED -> FeatureJoiner_5 [LEFT]
ProductionInstallationPermitDetails (reader MSSQL_ADO_1)
    attributes: Id identity, permitGranted bit, permitReconsidered bit, permitUpdated bit, dateOfGranting date, dateOfLastUpdate date, permitURL nvarchar(2048), enforcementAction nvarchar(500), installationId integer, controlFileId integer
    -> FeatureJoiner_4 [RIGHT]
FeatureJoiner_4
    ATTR_CONFLICT_RES = Use Left
    GEOMETRY_HANDLING = Use Left
    JOIN_KEYS = id installationId NUM
    JOIN_MODE = Inner
    JOINED -> ListBuilder_2
    UNJOINED_LEFT -> PythonCaller_3
ListBuilder_2
    GROUPS_ORDERED = No
    GROUP_BY = id
    LIST_ATTRS_TO_INCLUDE = dateOfGranting permitURL
    LIST_NAME = permits_list
    -> FeatureJoiner_5 [RIGHT]
FeatureJoiner_5
    ATTR_CONFLICT_RES = Use Left
    GEOMETRY_HANDLING = Use Left
    JOIN_KEYS = id id AUTO
    JOIN_MODE = Inner
    JOINED -> PythonCaller_3
PythonCaller_3
    NEW_ATTRIBUTES = text_line_data
    PYTHONSOURCE:
      import fme
      import fmeobjects
      from datetime import datetime

      # Template Class Interface:
      # When using this class, make sure its name is set as the value of
      # the 'Class or Function to Process Features' transformer parameter
      class FeatureProcessor(object):
          def __init__(self):
              self.xml_list = []
              self.text_line_data = ''
          def input(self,feature):
              otherActivity = ''
              permits = ''
              if feature.getAttribute('list_other_activity{}.otherActivity'):
                  for x in feature.getAttribute('list_other_activity{}.otherActivity'):
                      otherActivity += '                <EUReg:otherActivity xlink:href="http://dd.eionet.europa.eu/vocabulary/euregistryonindustrialsites/IEDAnnexIActivityValue/%s"></EUReg:otherActivity>\n'%(x,)
              if feature.getAttribute('permits_list{}.dateOfGranting'):
                  for i in range(len(feature.getAttribute('permits_list{}.dateOfGranting'))):
                      if len(feature.getAttribute('permits_list{%s}.dateOfGranting'%(i,))) != 0 and len(feature.getAttribute('permits_list{%s}.permitURL'%(i,))) !=0:
                          permits += '        <permit>\n\
                  <dateOfGranting>%s</dateOfGranting>\n\
                  <permitURL>%s</permitURL>\n\
              </permit>\n'%(datetime.strptime(feature.getAttribute('permits_list{%s}.dateOfGranting'%(i,)),'%Y%m%d').date(), feature.getAttribute('permits_list{%s}.permitURL'%(i,)))
                      elif len(feature.getAttribute('permits_list{%s}.dateOfGranting'%(i,))) != 0:
                          permits += '        <permit>\n\
                  <dateOfGranting>%s</dateOfGranting>\n\
              </permit>\n'%(datetime.strptime(feature.getAttribute('permits_list{%s}.dateOfGranting'%(i,)),'%Y%m%d').date())
                      elif len(feature.getAttribute('permits_list{%s}.permitURL'%(i,))) != 0:
                          permits += '        <permit>\n\
                  <permitURL>%s</permitURL>\n\
              </permit>\n'%(feature.getAttribute('permits_list{%s}.permitURL'%(i,)))
              tmp = '    <ProductionInstallation>\n\
              <countryId xlink:href="%s"></countryId>\n\
              <reportingYear>%s</reportingYear>\n\
              <inspireId>\n\
                  <localId>%s</localId>\n\
                  <namespace>%s</namespace>\n\
              </inspireId>\n\
              <pointGeometry>\n\
                  <gml:Point xmlns:gml="http://www.opengis.net/gml/3.2" gml:id="%s" srsDimension="2">\n\
                      <gml:pos>%s %s</gml:pos>\n\
                  </gml:Point>\n\
              </pointGeometry>\n\
              <installationName>\n\
                  <nameOfFeature>%s</nameOfFeature>\n\
              </installationName>\n\
              <IEDAnnexIActivity>\n\
                  <EUReg:IEDAnnexIActivityType>\n\
                      <EUReg:mainActivity xlink:href="http://dd.eionet.europa.eu/vocabulary/euregistryonindustrialsites/IEDAnnexIActivityValue/%s"></EUReg:mainActivity>\n%s\
                  </EUReg:IEDAnnexIActivityType>\n\
              </IEDAnnexIActivity>\n\
              <status>\n\
                  <pf:StatusType>\n\
                      <pf:statusType xlink:href="http://dd.eionet.europa.eu/vocabulary/euregistryonindustrialsites/ConditionOfFacilityValue/%s"></pf:statusType>\n\
                      <pf:validFrom xsi:nil="true"></pf:validFrom>\n\
                  </pf:StatusType>\n\
              </status>\n%s\
          </ProductionInstallation>' % (feature.getAttribute('countryCode'),\
          feature.getAttribute('reportingYear'),\
          feature.getAttribute('localId'),\
          feature.getAttribute('namespace'),\
          feature.getAttribute('gmlId'),\
          feature.getAttribute('y_4258'),\
          feature.getAttribute('x_4258'),\
          feature.getAttribute('installationName'),\
          feature.getAttribute('IEDAnnexIMainActivity'),\
          otherActivity,\
          feature.getAttribute('status'),\
          permits)
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PI_file [text_line]
PI_file: FeatureWriter
    DATASET = $(PRODUCTION_INSTALLATION_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    text_line -> FeatureHolder
ProductionInstallationPart (reader MSSQL_ADO_1)
    attributes: id identity, installationPartName nvarchar(200), installationPartNameConfidentiality varchar(25), plantType varchar(25), totalNominalCapacityAnyWaste float, permittedCapacityHazardous float, permittedCapacityNonHazardous float, specificConditions varchar(25), conditionsInformation nvarchar(500), specificConditionsPermitURL nvarchar(2048), totalRatedThermalInput float, localId varchar(200), namespace varchar(200), identifier varchar(200), identifierScheme varchar(200), x_3857 integer, y_3857 integer, x_4326 float, y_4326 float, x_4258 float, y_4258 float, shape_wm image, status varchar(25), remarks nvarchar(500), heatReleaseHazardousWaste bit, untreatedMunicipalWaste bit, publicDisclosure nvarchar(500), publicDisclosureURL nvarchar(2048), dateOfStartOfOperation date, installationId integer,
      gmlId varchar(200), controlFileId integer, countryCode varchar(2), reportingYear integer
    -> AttributeManager
    -> FeatureJoiner_6 [LEFT]
    -> FeatureJoiner_7 [LEFT]
ProductionInstallationPartDerogation (reader MSSQL_ADO_1)
    attributes: Id identity, derogation varchar(25), installationPartId integer, controlFileId integer
    -> FeatureJoiner_6 [RIGHT]
FeatureJoiner_6
    ATTR_CONFLICT_RES = Use Left
    GEOMETRY_HANDLING = Use Left
    JOIN_KEYS = id installationPartId NUM
    JOIN_MODE = Inner
    JOINED -> ListBuilder_3
    UNJOINED_LEFT -> PythonCaller_4
ListBuilder_3
    GROUPS_ORDERED = No
    GROUP_BY = id
    LIST_ATTRS_TO_INCLUDE = derogation
    LIST_NAME = derogation_list
    -> FeatureJoiner_7 [RIGHT]
FeatureJoiner_7
    ATTR_CONFLICT_RES = Use Left
    GEOMETRY_HANDLING = Use Left
    JOIN_KEYS = id id NUM
    JOIN_MODE = Inner
    JOINED -> PythonCaller_4
PythonCaller_4
    NEW_ATTRIBUTES = text_line_data
    PYTHONSOURCE:
      import fme
      import fmeobjects

      # Template Class Interface:
      # When using this class, make sure its name is set as the value of
      # the 'Class or Function to Process Features' transformer parameter
      class FeatureProcessor(object):
          def __init__(self):
              self.xml_list = []
              self.text_line_data = ''
          def input(self,feature):
              derogations = ''
              if feature.getAttribute('derogation_list{}.derogation'):
                  for x in feature.getAttribute('derogation_list{}.derogation'):
                      derogations += '        <derogations xlink:href="http://dd.eionet.europa.eu/vocabulary/euregistryonindustrialsites/DerogationValue/%s"></derogations>\n'%(x,)
              tmp = '    <ProductionInstallationPart>\n\
              <countryId xlink:href="%s"></countryId>\n\
              <reportingYear>%s</reportingYear>\n\
              <inspireId>\n\
                  <localId>%s</localId>\n\
                  <namespace>%s</namespace>\n\
              </inspireId>\n\
              <installationPartName>\n\
                  <nameOfFeature>%s</nameOfFeature>\n\
              </installationPartName>\n\
              <plantType xlink:href="http://dd.eionet.europa.eu/vocabulary/euregistryonindustrialsites/PlantTypeValue/%s"></plantType>\n\
              <pointGeometry>\n\
                  <gml:Point xmlns:gml="http://www.opengis.net/gml/3.2" gml:id="%s" srsDimension="2">\n\
                      <gml:pos>%s %s</gml:pos>\n\
                  </gml:Point>\n\
              </pointGeometry>\n\
              <status>\n\
                  <pf:statusType xlink:href="http://dd.eionet.europa.eu/vocabulary/euregistryonindustrialsites/ConditionOfFacilityValue/%s"></pf:statusType>\n\
      			<pf:validFrom xsi:nil="true"></pf:validFrom>\n\
              </status>\n%s\
          </ProductionInstallationPart>' % (feature.getAttribute('countryCode'),\
          feature.getAttribute('reportingYear'),\
          feature.getAttribute('localId'),\
          feature.getAttribute('namespace'),\
          feature.getAttribute('installationPartName'),\
          feature.getAttribute('plantType'),\
          feature.getAttribute('gmlId'),\
          feature.getAttribute('y_4258'),\
          feature.getAttribute('x_4258'),\
          feature.getAttribute('status'),\
          derogations)
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PIP_file [text_line]
PIP_file: FeatureWriter
    DATASET = $(PRODUCTION_INSTALLATION_PART_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    text_line -> FeatureHolder
ProductionSite (reader MSSQL_ADO_1)
    attributes: id identity, x_3857 integer, y_3857 integer, x_4326 float, y_4326 float, x_4258 float, y_4258 float, shape_wm image, localId varchar(200), namespace varchar(200), identifier varchar(200), identifierScheme varchar(200), siteName nvarchar(200), siteNameConfidentiality varchar(25), countryCode varchar(2), reportingYear integer, reportDataId integer, gmlId varchar(200), controlFileId integer
    -> PythonCaller
    -> AttributeManager
AttributeManager
    ATTR_TABLE = RENAME_SET_VALUE localId > siteLocalId
    -> FeatureJoiner [RIGHT]
FeatureJoiner
    ATTR_CONFLICT_RES = Use Left
    GEOMETRY_HANDLING = Use Left
    JOIN_KEYS = siteId id NUM
    JOIN_MODE = Inner
    JOINED -> PythonCaller_2
    UNJOINED_LEFT -> PythonCaller_2
PythonCaller_2
    NEW_ATTRIBUTES = text_line_data
    PYTHONSOURCE:
      import fme
      import fmeobjects

      # Template Class Interface:
      # When using this class, make sure its name is set as the value of
      # the 'Class or Function to Process Features' transformer parameter
      class FeatureProcessor(object):
          def __init__(self):
              self.xml_list = []
              self.text_line_data = ''
          def input(self,feature):
              tmp = '    <ProductionFacility>\n\
              <countryId xlink:href="%s"></countryId>\n\
              <reportingYear>%s</reportingYear>\n\
              <inspireId>\n\
                  <localId>%s</localId>\n\
                  <namespace>%s</namespace>\n\
              </inspireId>\n\
      		<geometry>\n\
                  <gml:Point xmlns:gml="http://www.opengis.net/gml/3.2" gml:id="%s" srsDimension="2">\n\
                      <gml:pos>%s %s</gml:pos>\n\
                  </gml:Point>\n\
              </geometry>\n\
              <facilityName>\n\
                  <nameOfFeature>%s</nameOfFeature>\n\
              </facilityName>\n\
      		<EUReg:parentCompany>\n\
      			<EUReg:ParentCompanyDetails>\n\
      				<EUReg:parentCompanyName>%s</EUReg:parentCompanyName>\n\
      				<EUReg:parentCompanyURL>%s</EUReg:parentCompanyURL>\n\
      				<EUReg:confidentialityReason xlink:href="http://dd.eionet.europa.eu/vocabulary/euregistryonindustrialsites/ReasonValue/%s"></EUReg:confidentialityReason>\n\
      			</EUReg:ParentCompanyDetails>\n\
      		</EUReg:parentCompany>\n\%s\
      		<EPRTRAnnexIActivity>\n\
      			<EUReg:EPRTRAnnexIActivityType>\n\
      				<EUReg:mainActivity xlink:href="http://dd.eionet.europa.eu/vocabulary/euregistryonindustrialsites/EPRTRAnnexIActivityValue/%s"></EUReg:mainActivity>\n\
      			</EUReg:EPRTRAnnexIActivityType>\n\
      		</EPRTRAnnexIActivity>\n\
      		<status>\n\
                  <pf:statusType xlink:href="http://dd.eionet.europa.eu/vocabulary/euregistryonindustrialsites/ConditionOfFacilityValue/%s"></pf:statusType>\n\
      			<pf:validFrom xsi:nil="true"></pf:validFrom>\n\
              </status>\n\
          </ProductionFacility>' % (feature.getAttribute('countryCode'),\
          feature.getAttribute('reportingYear'),\
          feature.getAttribute('localId'),\
          feature.getAttribute('namespace'),\
      	feature.getAttribute('gmlId'),\
          feature.getAttribute('y_4258'),\
          feature.getAttribute('x_4258'),\
      	feature.getAttribute('facilityName'),\
      	feature.getAttribute('parentCompanyName'),\
      	feature.getAttribute('parentCompanyURL'),\
      	feature.getAttribute('parentCompanyConfidentiality'),\
          '		<hostingSite xlink:href="%s"></hostingSite>\n' % (feature.getAttribute('siteLocalId'),) if feature.getAttribute('siteLocalId') else '',\
      	feature.getAttribute('EPRTRAnnexIMainActivity'),\
      	feature.getAttribute('status'))
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PF_file [text_line]
PF_file: FeatureWriter
    DATASET = $(PRODUCTION_FACILTY_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    text_line -> FeatureHolder
PythonCaller
    NEW_ATTRIBUTES = text_line_data
    PYTHONSOURCE:
      import fme
      import fmeobjects

      # Template Class Interface:
      # When using this class, make sure its name is set as the value of
      # the 'Class or Function to Process Features' transformer parameter
      class FeatureProcessor(object):
          def __init__(self):
              self.xml_list = []
              self.text_line_data = ''
          def input(self,feature):
              tmp = '    <ProductionSite>\n\
              <countryId xlink:href="%s"></countryId>\n\
              <reportingYear>%s</reportingYear>\n\
              <inspireId>\n\
                  <localId>%s</localId>\n\
                  <namespace>%s</namespace>\n\
              </inspireId>\n\
              <siteName>\n\
                  <nameOfFeature>%s</nameOfFeature>\n\
              </siteName>\n\
              <location>\n\
                  <gml:Point xmlns:gml="http://www.opengis.net/gml/3.2" gml:id="%s" srsDimension="2">\n\
                      <gml:pos>%s %s</gml:pos>\n\
                  </gml:Point>\n\
              </location>\n\
          </ProductionSite>' % (feature.getAttribute('countryCode'),\
          feature.getAttribute('reportingYear'),\
          feature.getAttribute('localId'),\
          feature.getAttribute('namespace'),\
          feature.getAttribute('siteName'),\
          feature.getAttribute('gmlId'),\
          feature.getAttribute('y_4258'),\
          feature.getAttribute('x_4258'))
              self.xml_list.append(tmp)
          def close(self):
              self.text_line_data = '<data xmlns:xsi="http://www.w3.org/2001/XMLSchema-instance" xmlns:xlink="http://www.w3.org/1999/xlink" xmlns:EUReg="http://dd.eionet.europa.eu/schemaset/euregistryonindustrialsites" xmlns:pf="http://inspire.ec.europa.eu/schemas/pf/4.0" xmlns:gml="http://www.opengis.net/gml/3.2">'
              self.text_line_data += '\n'
              for item in self.xml_list:
                  self.text_line_data +=  item
                  self.text_line_data += '\n'
              self.text_line_data += '</data>'

              newFeature = fmeobjects.FMEFeature()
              newFeature.setAttribute("text_line_data", self.text_line_data)
              self.pyoutput(newFeature)
    PYTHONSYMBOL = FeatureProcessor
    -> PS_file [text_line]
PS_file: FeatureWriter
    DATASET = $(PRODUCTION_SITE_FILE)
    DATASET_ATTR = _dataset
    FEATURE_TYPE_LIST_ATTR = _feature_type
    FORMAT = TEXTLINE
    SELECTED_PORTS = text_line
    TEXTLINE_COORDINATE_SYSTEM_GRANULARITY = FEATURE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    text_line -> FeatureHolder
FeatureHolder
    -> ZipArchiver
ZipArchiver
    FILE_PATH = $(PRODUCTION_SITE_FILE)
    MODE = REMOVE
    ZIP_PATH = $(ZIP_PATH)
    -> ZipArchiver_2
ZipArchiver_2
    FILE_PATH = $(PRODUCTION_INSTALLATION_FILE)
    MODE = APPEND
    ZIP_PATH = $(ZIP_PATH)
    -> ZipArchiver_3
ZipArchiver_3
    FILE_PATH = $(PRODUCTION_INSTALLATION_PART_FILE)
    MODE = APPEND
    ZIP_PATH = $(ZIP_PATH)
    -> ZipArchiver_4
ZipArchiver_4
    FILE_PATH = $(PRODUCTION_FACILTY_FILE)
    MODE = APPEND
    ZIP_PATH = $(ZIP_PATH)

FME custom transformer ZipArchiver
Compresses a file or folder and appends it into the specified zip file.
    The archive name will be the same as the target file name. If a file having the same name as the target file has been archived in the zip file already, the file will not be archived.
    The transformer creates a new zip file when receiving the first file that should be archived into it, if the specified zip file doesn't exist. 
    -----
    Note: This transformer has been basically internationalized with 2016-01-22 update. However, depending on the environment (platform, OS version etc.), file path strings containing Non-ASCII characters still may not be treated correctly. Please test enough if the path strings may contain Non-ASCII characters.
    -----
    Input features will be output through the Output port as-is.
    The transformer creates log features which contain these attributes for each file, and outputs them from the LogSuccess/LogFailure port.
    - Result: "success" if the file was archived successfully, "failure" otherwise.
    - Target File: the target file path.
    - Zip File: the zip file path.
    - Archive Name: the archive name of the target file in the zip file if archived successfully, empty otherwise.
    - Comment: compression ratio if archived successfully, failure reason otherwise.
    ファイルまたはフォルダを圧縮し、指定したzipファイルに追加します。
    アーカイブ名は対象のファイル名と同じになります。対象とするファイルと同じ名前のファイルがすでにzipファイルにアーカイブされていた場合、そのファイルはアーカイブされません。
    指定したzipファイルが存在しない場合、このトランスフォーマーはそれにアーカイブすべき最初のファイルを受け取ったときに新しいzipファイルを作成します。
-----
    注: 2016-01-22 の更新によって、このトランスフォーマーは基本的には国際化されました。しかし、環境（プラットフォームやOSのバージョンなど）によっては、ASCII文字（半角の英数字や記号）以外の文字を含むファイルパス文字列ま、まだ正しく処理されない可能性があります。パス文字列に非ASCII文字が含まれる可能性がある場合は、十分にテストしてください。
-----
    入力フィーチャーはそのままOutputポートから出力されます。
    このトランスフォーマーは、次の属性を持つログフィーチャーをファイルごとに作成し、LogSuccess/LogFailureポートから出力します。
    - Result: ファイルが正常にアーカイブされた場合は"succcess"、そうでない場合は"failure"
    - Target File: 対象のファイルパス
    - Zip File: zipファイルパス
    - Archive Name: アーカイブに成功した場合はzipファイル内でのアーカイブ名、失敗した場合は空文字列
    - Comment: アーカイブに成功した場合は圧縮率、失敗した場合はその理由
Parameters 
    Target File or Folder
    : 
    Specify a file or folder path that should be archived. You can also set a feature attribute value to this parameter.
    If you specify a folder path here, all files under the folder will be archived. In the case, the original directory structure will also be preserved, and the archive name of the file will contain path starting from the specified folder.
    アーカイブするファイルまたはフォルダのパスを指定します。フィーチャーの属性をこのパラメーターに設定することもできます。 
    ここにフォルダのパスを指定した場合は、そのフォルダ以下にある全てのファイルがアーカイブされます。その場合、元のディレクトリ構造も維持され、ファイルのアーカイブ名には、指定されたフォルダから始まるパスが含まれます。
    Destination Zip File
    : 
    Specify a zip file path (*.zip). You can also set a feature attribute value to this parameter.
    If the extension of the specified file path is not "zip", the transformer will add ".zip" to the path automatically. 
    zipファイルパス（*.zip）を指定します。フィーチャーの属性をこのパラメーターに設定することもできます。 
    指定されたパスの拡張子が"zip"でない場合は、そのパスに".zip"を自動的に付加します。
    If Destination Zip File Exists
    :
    If the specified destination zip file exists at the translation starting time, this transformer appends compressed files into the existing zip file, by default. If you set 
    "Remove Existing Zip File"
    to this parameter, this transformer removes the existing zip file once at first, and then appends compressed files into the newly created same name zip file. If you set 
    "Rename Destination Zip File"
    , an suffix will be added to the destination zip file name automatically to differentiate from the existing zip file.
    変換の開始時に指定されたzipファイルが存在する場合、デフォルトでは、このトランスフォーマーは既存のzipファイルに圧縮したファイルを追加します。このパラメーターに 
    "Remove Existing Zip File"
    を設定した場合は、このトランスフォーマーは最初に一回だけ既存のzipファイルを削除してから、新たに作成した同じ名前のzipファイルに圧縮したファイルを追加します。
    "Rename Destination Zip File"
    を設定した場合は、既存のzipファイルと区別するため、出力先のzipファイル名にサフィクスが自動的に付加されます。

Parameters:
- FILE_PATH =   # Target File or Folder
- ZIP_PATH =   # Destination Zip File
- MODE = APPEND

Input (input)
    -> ParameterFetcher
ParameterFetcher
    ATTR_LIST = __ziparchiver.filepath {$(FILE_PATH)} __ziparchiver.zippath {$(ZIP_PATH)} __ziparchiver.mode {$(MODE)}
    -> PythonCaller
PythonCaller
    NEW_ATTRIBUTES = __ziparchiver.result
    PYTHONSOURCE:
      import fme
      import fmeobjects
      import os, zipfile

      # 2018-07-12, Takashi Iijima, Allow Zip64 by default. Thanks to David R.
      # 2018-05-02, Takashi Iijima, Avoided 'divided by 0' error that occurred if the original file size was zero.
      # 2016-01-22, Takashi Iijima, Refactoring and Internationalizing (Tech Preview)
      # 2015-05-24, Takashi Iijima, Original Implementation

      class ZipArchiver(object):
          def __init__(self):
              import platform
              majorVersion = int(platform.python_version_tuple()[0])
              if majorVersion < 3:
                  import locale
                  t = locale.getdefaultlocale()
                  self.encode = lambda s: (s.encode(t[1]) if t else s) if isinstance(s, unicode) else s
              else:
                  self.encode = lambda s: s
              self.logger = fmeobjects.FMELogFile()
              self.zpaths = {} # key: specified zip file path (lower-case), value: treated zip file path in this session

          def input(self, feature):
              try:
                  # Retrieve target file path and zip file path from feature attributes.
                  # If the specified zip file path doesn't end with ".zip", add the extension.
                  regulatePath = lambda path: os.path.abspath(path).replace('\\', '/')
                  fpath = regulatePath(feature.getAttribute('__ziparchiver.filepath'))
                  zpath = regulatePath(feature.getAttribute('__ziparchiver.zippath'))
                  if not zpath.lower().endswith('.zip'):
                      zpath = '%s.zip' % zpath
                  keyPath = zpath.lower()

                  mode = feature.getAttribute('__ziparchiver.mode')
                  if os.path.exists(zpath):
                      if mode == 'REMOVE':
                          if keyPath not in self.zpaths:
                              os.remove(zpath)
                      elif mode == 'RENAME':
                          if keyPath in self.zpaths:
                              zpath = self.zpaths[keyPath]
                          else:
                              format, n = '%s_%d.zip', 1
                              while os.path.exists(format % (zpath[:-4], n)): n += 1
                              zpath = format % (zpath[:-4], n)
                  self.zpaths[keyPath] = zpath

                  # Collect  target file paths, including empty directries if "fpath" is a directory.
                  # If specifid file/directory doesn't exist, throw an error.
                  root = ''
                  fpaths, dpaths = [], []
                  if os.path.exists(fpath): # fpath is a file
                      root = os.path.split(fpath)[0]
                      if os.path.isfile(fpath):
                          fpaths = [fpath]
                      elif os.listdir(fpath): # fpath is a non-empty directory
                          for dirpath, dirnames, filenames in os.walk(fpath):
                              paths = [os.path.join(dirpath, d) for d in dirnames]
                              dpaths += [regulatePath(path) for path in paths if not os.listdir(path)]
                              fpaths += [regulatePath(os.path.join(dirpath, f)) for f in filenames]
                      else: # fpath is an empty directory
                          dpaths = [fpath]
                  else:
                      raise Exception('specified file doesn\'t exist.')

                  # If destination directory doesn't exist, create the directory.
                  if not os.path.exists(os.path.split(zpath)[0]):
                      os.makedirs(os.path.split(zpath)[0])

                  # Then, perform archiving.
                  with zipfile.ZipFile(zpath, 'a', zipfile.ZIP_DEFLATED, allowZip64=True) as zipper:
                      for path in [path for path in fpaths if path.lower() != zpath.lower()]:
                          aname = path[len(root) + 1:] # archive name
                          result, msg = False, ''
                          try:
                              info = zipper.getinfo(aname)
                              msg = '"%s" exists in the archive already.' % aname
                          except:
                              try:
                                  zipper.write(path, aname)
                                  info = zipper.getinfo(aname)
                                  after = info.compress_size/1024.0
                                  before = info.file_size/1024.0
                                  rate = ('%.1f%%' % (after/before*100.0)) if 0 < before else 'N/A'
                                  msg = '%s (%.1f / %.1f KB)' % (rate, after, before)
                                  result = True
                              except Exception as ex:
                                  msg = '%s' % ex
                          self.outputLogFeature('Success' if result else 'Failure', path, zpath, aname, msg)
                      for path in dpaths:
                          aname = path[len(root) + 1:] # archive name
                          try:
                              info = zipper.getinfo(aname)
                          except:
                              zipper.write(path, aname)
              except Exception as ex:
                  self.outputLogFeature('Terminate', fpath, zpath, '', '%s' % ex)
              finally: # always output the input feature through the Output port.
                  self.pyoutput(feature)

          # Output a log feature.
          def outputLogFeature(self, flag, fpath, zpath, aname, msg):
              if flag != 'Success':
                  self.logger.logMessageString(self.encode('ZipArchiver: %s' % msg), \
                      fmeobjects.FME_ERROR if flag == 'Terminate' else fmeobjects.FME_WARN)
              feature = fmeobjects.FMEFeature()
              feature.setAttribute('__ziparchiver.result', flag.lower())
              feature.setAttribute('Target File', fpath)
              feature.setAttribute('Zip File', zpath)
              feature.setAttribute('Archive Name', aname if flag == 'Success' else '')
              feature.setAttribute('Comment', msg)
              feature.setAttribute('fme_feature_type', 'ZipArchiver_%s' % flag)
              self.pyoutput(feature)
    PYTHONSYMBOL = ZipArchiver
    -> Tester
Tester
    BOOL_OP = OR
    TEST_CLAUSE = TEST __ziparchiver.result ATTRIBUTE_IS_MISSING ""
    PASSED -> Output (output)
    FAILED -> AttributeRenamer
Output (output)
AttributeRenamer
    ATTR_LIST = __ziparchiver.result,Result,
    -> AttributeExposer
AttributeExposer
    ATTR_LIST = "Target File","Zip File","Archive Name",Comment
    -> AttributeKeeper
AttributeKeeper
    KEEP_ATTRS = Archive Name,Comment,Result,Target File,Zip File
    -> AttributeFilter
AttributeFilter
    ATTR_NAME = Result
    ATTR_VALUES = success,failure,terminate,<EMPTY>,<MISSING>,<NULL>,<UNFILTERED>
    success -> LogSuccess (output)
    failure -> LogFailure (output)
    terminate -> Terminator
LogSuccess (output)
LogFailure (output)
Terminator
    MESSAGE = @Value(Comment)
